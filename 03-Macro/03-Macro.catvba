Attribute VB_Name = "Console_de_commande"
Attribute VB_Base = "0{D79A0885-3C2C-485C-B405-1FD8ABCFAB9A}{9681C687-6E50-4A63-AF94-2BB372606E55}"
Attribute VB_GlobalNameSpace = False
Attribute VB_Creatable = False
Attribute VB_PredeclaredId = True
Attribute VB_Exposed = False
Attribute VB_TemplateDerived = False
Attribute VB_Customizable = False

Private Sub Changement_Click()
Console_de_commande.Hide
End Sub
Private Sub Direction_Change()
valeur_direction = Direction.Value
Console_de_commande.Hide
End Sub

Private Sub MoveButton_Change()
MsgBox ("Pas encore en fonctionnement")
End Sub

Private Sub ScrollBarVerin1_Change()
valeur_bras = ScrollBarVerin1.Value
Console_de_commande.Hide
End Sub

Private Sub ScrollBarVerin2_Change()
valeur_avant_bras = ScrollBarVerin2.Value
Console_de_commande.Hide
End Sub

Private Sub ScrollBarVerin3_Change()
valeur_godet = ScrollBarVerin3.Value
Console_de_commande.Hide
End Sub

Private Sub Stop_Button_Click()
creation = "Stop"
Console_de_commande.Hide
End Sub

Private Sub TourelleButton_Change()
valeur_tourelle = TourelleButton.Value
Console_de_commande.Hide
End Sub


Private Sub UserForm_Activate()
MsgBox "Quels changements appliquer ?"
End Sub

Attribute VB_Name = "Pilotage_pelleteuse_true"
Sub CATmain()

Dim productDocument1 As ProductDocument
Set productDocument1 = CATIA.ActiveDocument    ' Le document ouvert dans CATIA

Dim product1 As AnyObject
Set product1 = productDocument1.Product         'Le produit racine (rootproduct) du document CATIA

Dim products1 As Products
Set products1 = product1.Products               'La collection de tous les composants de l'assemblage


'lister tous les noms des composants: pour activer la liste il faut supprimer les ' des 4 lignes suivantes

'Dim i As Integer
'For i = 1 To products1.Count
'   MsgBox ("Composant numéro: " & i & " ->  " & products1.Item(i).Name)
'Next

Set mecanisme = product1.GetTechnologicalObject("Mechanisms") 'Récupération de la collection des mécanismes dans le product

'Vérification du nombre de mécanisme dans le document

'Dim nbmeca As Integer
'nbmeca = mecanisme.Count
'    MsgBox ("il y a " & nbmeca & " mécanisme")

Set pilotage = mecanisme.Item(1)

'Vérification de la lecture de toutes les commandes

'Dim i As Integer
'For i = 1 To pilotage.Commands.Count
'    MsgBox ("Commande numéro " & i & " de nom " & pilotage.Commands.Item(i).Name & " de valeur " & pilotage.Commands.Item(i).CurrentValue)
'Next

'Création de la liste des valeurs de commande

NbCommandes = pilotage.NbCommands - 1
ReDim varPosition(NbCommandes)
pilotage.GetCommandValues varPosition

'Vérification que toutes les valeurs des commandes se trouvent bien dans la liste varPosition

'Dim i As Integer
'For i = 0 To 13
'MsgBox (varPosition(i))
'Next

'Exemple comment modifier une commande
'varPosition(8) = 90
'pilotage.PutCommandValues varPosition

MsgBox "ready?"
creation = "Start"
While creation = "Start"
    Console_de_commande.Show
    varPosition(4) = valeur_direction
    varPosition(5) = -valeur_direction
    varPosition(6) = valeur_direction
    varPosition(7) = -valeur_direction
    varPosition(8) = valeur_tourelle
    varPosition(10) = valeur_bras
    varPosition(11) = valeur_avant_bras
    varPosition(12) = valeur_godet
    pilotage.PutCommandValues varPosition
Wend


End Sub

Attribute VB_Name = "Savoir_comment_ca_sappelle"
Sub CATmain()
Dim oSel As Selection
Set oSel = CATIA.ActiveDocument.Selection
MsgBox "Number of objects selected: " & oSel.Count
Dim i As Integer
For i = 1 To oSel.Count
Dim oSelEl As SelectedElement
Set oSelEl = oSel.Item(i)
MsgBox " The selected element's name is " & oSelEl.Value.Name
MsgBox "The Selected element's type is " & oSelEl.Type
Next
oSel.Clear
End Sub

Attribute VB_Name = "module_des_variables"
Public creation As String
Public valeur_tourelle As Long
Public valeur_bras As Long
Public valeur_avant_bras As Long
Public valeur_godet As Long
Public valeur_direction As Long
