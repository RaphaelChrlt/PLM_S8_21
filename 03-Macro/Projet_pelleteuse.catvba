Attribute VB_Name = "Console_de_commande"
Attribute VB_Base = "0{F064209C-5140-404C-A967-5633BA58F3B7}{11442160-55CF-4A2D-B4E9-707B574B4975}"
Attribute VB_GlobalNameSpace = False
Attribute VB_Creatable = False
Attribute VB_PredeclaredId = True
Attribute VB_Exposed = False
Attribute VB_TemplateDerived = False
Attribute VB_Customizable = False
Private Sub Label1_Click()

End Sub

Attribute VB_Name = "Fichier_de_pilotage"
Sub CATMain()

End Sub
